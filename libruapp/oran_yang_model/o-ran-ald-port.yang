module o-ran-ald-port {
  yang-version 1.1;
  namespace "urn:o-ran:ald-port:1.0";
  prefix "o-ran-ald-port";

  organization "O-RAN Alliance";

  contact
    "www.o-ran.org";

  description
    "This module defines the input state and output configuration for
    the Antenna Line Device capability.

    Copyright 2021 the O-RAN Alliance.

    THIS SOFTWARE IS PROVIDED BY THE COPYRIGHT HOLDERS AND CONTRIBUTORS 'AS IS'
    AND ANY EXPRESS OR IMPLIED WARRANTIES, INCLUDING, BUT NOT LIMITED TO, THE
    IMPLIED WARRANTIES OF MERCHANTABILITY AND FITNESS FOR A PARTICULAR PURPOSE
    ARE DISCLAIMED. IN NO EVENT SHALL THE COPYRIGHT HOLDER OR CONTRIBUTORS BE
    LIABLE FOR ANY DIRECT, INDIRECT, INCIDENTAL, SPECIAL, EXEMPLARY, OR
    CONSEQUENTIAL DAMAGES (INCLUDING, BUT NOT LIMITED TO, PROCUREMENT OF
    SUBSTITUTE GOODS OR SERVICES; LOSS OF USE, DATA, OR PROFITS; OR BUSINESS
    INTERRUPTION) HOWEVER CAUSED AND ON ANY THEORY OF LIABILITY, WHETHER IN
    CONTRACT, STRICT LIABILITY, OR TORT (INCLUDING NEGLIGENCE OR OTHERWISE)
    ARISING IN ANY WAY OUT OF THE USE OF THIS SOFTWARE, EVEN IF ADVISED OF THE
    POSSIBILITY OF SUCH DAMAGE.

    Redistribution and use in source and binary forms, with or without
    modification, are permitted provided that the following conditions are met:

    * Redistributions of source code must retain the above copyright notice,
    this list of conditions and the above disclaimer.
    * Redistributions in binary form must reproduce the above copyright notice,
    this list of conditions and the above disclaimer in the documentation
    and/or other materials provided with the distribution.
    * Neither the Members of the O-RAN Alliance nor the names of its
    contributors may be used to endorse or promote products derived from
    this software without specific prior written permission.";

  revision "2021-03-22" {
    description
      "version 1.2.0

      1) typographical corrections in descriptions.";

    reference "ORAN-WG4.M.0-v01.00";
  }

  revision "2019-07-03" {
    description
      "version 1.1.0

      1) backward compatible changes to introduce groupings.";

    reference "ORAN-WG4.M.0-v01.00";
  }

  revision "2019-02-04" {
    description
      "version 1.0.0

      1) imported model from xRAN
      2) changed namespace and reference from xran to o-ran";

    reference "ORAN-WG4.M.0-v01.00";
  }


  feature OVERCURRENT-SUPPORTED {
    description
      "This feature indicates that the equipment supports the over-current notification
      capability.";
  }

// Groupings

  grouping aldport-group {
    leaf over-current-supported {
      type boolean;
      config false;
      description
        "Set to TRUE when the equipment supports overcurrent notifications";
    }

    list ald-port {
      key "name";

      config false;

      description
        "Leaf nodes describing ALD Port";
      leaf name {
        type string {
          length "1..255";
        }
        description
          "A name that is unique that identifies a ald port instance.
          This name may be used in fault management to refer to a fault source
          or affected object";
      }

      leaf port-id {
        type uint8;
            config false;
            mandatory true;

            description
          "A number which identifies an ALD Port.
          The number of the Physical ALD port connector in the module.
          If the module supports 2 ALD Port connectors, use 0 and 1.";
      }

      leaf dc-control-support{
        type boolean;
        config false;
            mandatory true;

            description
          "It is shown that on/off in the DC power supply is possible.
          In case of False, power supply is always on.";
      }

      leaf dc-enabled-status {
        when "../dc-control-support = 'true'";
        type boolean;
        default false;
        description
          "Status of DC voltage enabled on antenna line.
          Valid only in case dc-control-support is true.";
      }

      leaf supported-connector{
        type enumeration {
              enum ANTENNA_CONNECTOR {
                description
                    "This ald port is related to antenna connector";
              }
              enum RS485_PORT {
                description
                    "This ald port is related to RS485 port";
              }
            }
        config false;
            mandatory true;

            description
          "Informs about the connectors of Module which ALDs are connected to.
          This value is depending on HW design.";
      }
    }

    list ald-port-dc-control {
      key "name";

      description
        "Container needed to manage DC on ALD ports";

      leaf name {
        type leafref {
          path "/ald-ports-io/ald-port/name";
          require-instance false;
        }
        mandatory true;

        description
          "Name derived from unmodifiable list ald-port";
      }

      leaf dc-enabled{
        type boolean;

        description
          "If dc-control-support is true case, this leaf is effective.
          If dc-control-support is not true this leaf makes no action
          In case of true, the power supply shall be turned on.";
      }
    }
  }

  grouping overcurrent-group {
    container overload-condition {
      description
        "Container used in notification";

      leaf-list overloaded-ports {
        type leafref {
          path "/ald-ports-io/ald-port/name";
        }
        description
          "List of overloaded ports";
      }
    }
  }

  grouping dc-enabled-group {
    list ald-port {
      key name;
      description
        "list of ald-ports that has its dc-enabled-status changed";
      leaf name{
        type leafref {
          path "/ald-ports-io/ald-port/name";
        }
        description "Name of port which has changed";
      }
      leaf dc-enabled-status{
        type leafref {
          path "/ald-ports-io/ald-port/dc-enabled-status";
        }
        description "New staus of dc-enabled-status";
      }
    }
  }

// Top Level Container

  container ald-ports-io {
    description
      "ALD port information.
       ALD port of the equipment that can be used to connect External Equipment (Antenna Line Devices).
       Communication uses AISG over HDLC.
       Physical connection depends on connector type offered by the port (RS-485 or antenna line)
       Note: Single instance of ALD Port can point to more than one antenna line devices.";

    uses aldport-group;
  }

  notification overcurrent-report {
    if-feature OVERCURRENT-SUPPORTED;

    description
      "The equipment is able to report overcurrent condition about Port.
      This function is depending on HW design.
      The notification depend on power consumption which connected ALD devices and module.";

    uses overcurrent-group;
  }

  notification dc-enabled-status-change {
    description
      "The equipment is able to report the change of 'dc-enabled-status' of the ald-port.
      This is applicable when the leaf 'dc-control-support' of the ald-pot is 'TRUE'.";

    uses dc-enabled-group;
  }
}
